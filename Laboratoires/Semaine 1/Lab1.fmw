FME workspace Lab1.fmw

Parameters:
- SourceDataset_CSV2 = https://donnees.montreal.ca/dataset/c1d65779-d3cb-44e8-af0a-b9f2c5f7766d/resource/28a4957d-732e-48f9-8adb-0624867d9bb0/download/businesses.csv   # Source CSV (Comma Separated Value) File(s)
- DestDataset_POSTGIS = GEO7630   # Connection
- SourceDataset_GEOJSON = https://donnees.montreal.ca/dataset/43146e84-aaed-4552-87bf-e03954b81c20/resource/2b8bf94c-6b9a-4d60-8091-5b82467a4138/download/lieux-fr.geojson   # Source GeoJSON File or URL
- DestDataset_POSTGIS_3 = GEO7630   # Connection

Readers:
- CSV2_1: CSV2 from $(SourceDataset_CSV2)
- GEOJSON_1: GEOJSON from $(SourceDataset_GEOJSON)

Writers:
- POSTGIS_1: POSTGIS to $(DestDataset_POSTGIS)
- POSTGIS_2: POSTGIS to $(DestDataset_POSTGIS_3)

CSV (reader CSV2_1)
    attributes: business_id uint32, name varchar(80), address varchar(48), city varchar(21), state varchar(15), type varchar(57), statut varchar(30), date_statut uint32, latitude y_coordinate, longitude x_coordinate, x real64, y real64
    -> Lab1 (writer POSTGIS_1)
Lab1 (writer POSTGIS_1)
    attributes: business_id int8, name varchar(80), address varchar(48), city varchar(21), state varchar(15), type varchar(57), statut varchar(30), date_statut int8, latitude float8, longitude float8, x float8, y float8
lieux-fr (reader GEOJSON_1)
    attributes: titre_lieu string, url_fiche string, description string, date_cree string, date_revision string, arrondissements string, types string, installations string, activites string, commodites string, accessibilite string, categories string, statut_ouverture string, horaire_par_jour string, commentaires_horaire string, reglementation string, paiement string, telephone string, courriel string, titre_lieu_adresse_postale string, adresse_principale string, adresse_secondaire string, code_postal string, ville string, long float, lat float, X string, Y string
    -> lieuxpublics (writer POSTGIS_2)
lieuxpublics (writer POSTGIS_2)
    attributes: titre_lieu varchar, url_fiche varchar, description varchar, date_cree varchar, date_revision varchar, arrondissements varchar, types varchar, installations varchar, activites varchar, commodites varchar, accessibilite varchar, categories varchar, statut_ouverture varchar, horaire_par_jour varchar, commentaires_horaire varchar, reglementation varchar, paiement varchar, telephone varchar, courriel varchar, titre_lieu_adresse_postale varchar, adresse_principale varchar, adresse_secondaire varchar, code_postal varchar, ville varchar, long float8, lat float8, x varchar, y varchar
